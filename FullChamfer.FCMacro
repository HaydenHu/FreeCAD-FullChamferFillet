# -*- coding: utf-8 -*-
# Macro: FullChamfer
# 图标: 完全倒角
# 功能: 对选中的边执行倒角。
#       半径 < 最小邻边长 → 使用 FreeCAD 自带 PartDesign Chamfer
#       半径 >= 最小邻边长 → 构造切割体 + 布尔差集（完全倒角）
#
# 使用方法:
#   1. 在 PartDesign 工作台中选中一条或多条边
#   2. 运行此宏
#   3. 输入倒角距离（默认=相邻面最小边长=完全倒角）

import FreeCAD as App
import FreeCADGui as Gui
import Part
from FreeCAD import Vector
from PySide import QtGui, QtCore

def get_adjacent_faces(edge, shape):
    """获取包含此边的所有面（不依赖顶点，圆形边也适用）."""
    mid_p = (edge.FirstParameter + edge.LastParameter) / 2.0
    mid_pt = edge.valueAt(mid_p)
    faces = []
    for f in shape.Faces:
        try:
            d, _, _ = f.distToShape(Part.Vertex(mid_pt))
            if d < 1e-5:
                faces.append(f)
        except Exception:
            pass
    return faces


def edges_same(e1, e2, tol=1e-5):
    """判断两条边是否是同一条."""
    mid1 = (e1.FirstParameter + e1.LastParameter) / 2.0
    mid2 = (e2.FirstParameter + e2.LastParameter) / 2.0
    if e1.valueAt(mid1).distanceToPoint(e2.valueAt(mid2)) > tol:
        return False
    return abs(e1.Length - e2.Length) < tol


def get_min_adjacent_edge_length(selected_edge, shape):
    min_len = float('inf')
    for face in get_adjacent_faces(selected_edge, shape):
        for other_edge in face.Edges:
            if edges_same(other_edge, selected_edge):
                continue
            L = other_edge.Length
            if L > 1e-7 and L < min_len:
                min_len = L
    return min_len if min_len != float('inf') else 0.0


def find_body(obj):
    if obj.TypeId == 'PartDesign::Body':
        return obj
    for p in obj.InList:
        if p.TypeId == 'PartDesign::Body':
            return p
    try:
        g = obj.getParentGroup()
        if g and g.TypeId == 'PartDesign::Body':
            return g
    except Exception:
        pass
    return None


def get_tip(body):
    if hasattr(body, 'Tip') and body.Tip:
        return body.Tip
    for o in reversed(body.Group):
        if hasattr(o, 'Shape') and not o.Shape.isNull():
            return o
    return None


def create_chamfer_cutter(shape, edge_idx, chamfer_dist):
    """构造倒角切割楔体（直线边可用，圆形边会报错）."""
    edge = shape.Edges[edge_idx]
    d = chamfer_dist

    # 获取边的起终点（参数方式，兼容圆形边）
    fp = edge.FirstParameter
    lp = edge.LastParameter
    v0 = edge.valueAt(fp)
    v1 = edge.valueAt(lp)
    # 圆形边起终点相同，取半圈位置
    if v0.distanceToPoint(v1) < 1e-5:
        v1 = edge.valueAt(fp + (lp - fp) / 2.0)

    # 边方向取中点切线
    mid_p = (fp + lp) / 2.0
    ev = edge.tangentAt(mid_p)
    ev.normalize()

    # 相邻面
    adj_faces = get_adjacent_faces(edge, shape)
    normals = []
    for f in adj_faces:
        n = f.normalAt(0.5, 0.5)
        normals.append(n)

    if len(normals) < 2:
        raise RuntimeError("边至少需要两个相邻面")

    n0, n1 = normals[0], normals[1]
    for i, (n, f) in enumerate([(n0, adj_faces[0]), (n1, adj_faces[1])]):
        center = f.CenterOfMass
        if n.dot(center - v0) < 0:
            normals[i] = -n
    n0, n1 = normals[0], normals[1]

    cut0 = -n0
    cut1 = -n1
    ext = 5.0

    pts_start = [
        v0 - ev * ext,
        v0 + cut0 * (d + 2) - ev * ext,
        v0 + cut1 * (d + 2) - ev * ext,
    ]
    pts_end = [
        v1 + ev * ext,
        v1 + cut0 * (d + 2) + ev * ext,
        v1 + cut1 * (d + 2) + ev * ext,
    ]
    pts_all = pts_start + pts_end

    def mkface(ix):
        poly = Part.makePolygon([pts_all[i] for i in ix] + [pts_all[ix[0]]])
        return Part.Face(Part.Wire(poly))

    fs = [
        mkface([0, 1, 2]),
        mkface([3, 4, 5]),
        mkface([0, 1, 4, 3]),
        mkface([0, 2, 5, 3]),
        mkface([1, 2, 5, 4]),
    ]

    shell = Part.makeShell(fs)
    if shell.isNull():
        raise RuntimeError("无法创建切割壳体")
    solid = Part.makeSolid(shell)
    if solid is None or solid.isNull():
        raise RuntimeError("无法创建切割实体")
    return solid


def main():
    doc = App.ActiveDocument
    if not doc:
        QtGui.QMessageBox.warning(None, "错误", "请先打开文档。")
        return

    sel = Gui.Selection.getSelectionEx()
    if not sel:
        QtGui.QMessageBox.warning(None, "错误", "请先选中一条或多条边。")
        return

    edge_list = []
    for s in sel:
        if not hasattr(s.Object, 'Shape'):
            continue
        obj = s.Object
        shape = obj.Shape
        body = find_body(obj)
        for sn in s.SubElementNames:
            if sn.startswith('Edge'):
                try:
                    edge_list.append({
                        'edge': shape.getElement(sn),
                        'shape': shape,
                        'body': body,
                        'obj': obj,
                        'sub': sn,
                    })
                except Exception:
                    pass

    if not edge_list:
        QtGui.QMessageBox.warning(None, "错误", "未获取到有效边。")
        return

    def get_default_chamfer_dist(edge, shape):
        """获取默认倒角距离：圆边用圆半径，直边用最小邻边长."""
        # 检查是否是圆形边
        try:
            c = edge.Curve
            if hasattr(c, 'Radius') and c.Radius > 0:
                return c.Radius, True  # 圆形边
        except Exception:
            pass
        min_l = get_min_adjacent_edge_length(edge, shape)
        return min_l, False  # 直边

    edge_data = []
    for eo in edge_list:
        default_d, is_circle = get_default_chamfer_dist(eo['edge'], eo['shape'])
        min_l = get_min_adjacent_edge_length(eo['edge'], eo['shape'])
        if default_d < 1e-7:
            QtGui.QMessageBox.warning(None, "错误",
                f"边 {eo['sub']} 无法计算参数。")
            return
        edge_data.append({'eo': eo, 'default_d': default_d,
                          'min_len': min_l, 'is_circle': is_circle})

    # 对话框
    dlg = QtGui.QDialog()
    dlg.setWindowTitle("完全倒角")
    dlg.setMinimumWidth(380)
    dlg.setModal(True)
    layout = QtGui.QVBoxLayout()

    layout.addWidget(QtGui.QLabel(
        f"<b>完全倒角</b><br>已选中 {len(edge_list)} 条边"))
    layout.addSpacing(8)

    dist_layout = QtGui.QHBoxLayout()
    dist_layout.addWidget(QtGui.QLabel("倒角距离 (mm):"))
    dist_spin = QtGui.QDoubleSpinBox()
    dist_spin.setRange(0.001, 99999.0)
    dist_spin.setDecimals(4)
    dist_spin.setSingleStep(0.1)
    dist_spin.setValue(edge_data[0]['default_d'])
    dist_layout.addWidget(dist_spin)
    layout.addLayout(dist_layout)

    layout.addSpacing(4)

    info_text = "各边参数:\n"
    for i, ed in enumerate(edge_data):
        typ = "圆边" if ed['is_circle'] else "直边"
        info_text += (f"  边 {i + 1} ({typ}): 默认 {ed['default_d']:.4f} mm"
                      f"  最小邻边长 {ed['min_len']:.4f} mm\n")
    layout.addWidget(QtGui.QLabel(info_text))

    layout.addSpacing(4)

    # 方法提示
    method_label = QtGui.QLabel("")
    layout.addWidget(method_label)

    def update_hint():
        d = dist_spin.value()
        ml = edge_data[0]['min_len']
        if d < ml:
            method_label.setText(
                f"<span style='color:#228833;'>使用 PartDesign Chamfer（标准特征）</span>")
        else:
            method_label.setText(
                f"<span style='color:#cc8800;'>使用布尔切割（完全倒角）</span>")
        method_label.setTextFormat(QtCore.Qt.RichText)

    dist_spin.valueChanged.connect(lambda v: update_hint())
    update_hint()

    layout.addSpacing(8)

    btn_layout = QtGui.QHBoxLayout()
    ok = QtGui.QPushButton("执行倒角")
    ok.clicked.connect(dlg.accept)
    cancel = QtGui.QPushButton("取消")
    cancel.clicked.connect(dlg.reject)
    btn_layout.addWidget(ok)
    btn_layout.addWidget(cancel)
    layout.addLayout(btn_layout)
    dlg.setLayout(layout)

    if dlg.exec_() != QtGui.QDialog.Accepted:
        return

    chamfer_dist = dist_spin.value()
    if chamfer_dist <= 0:
        return

    d = chamfer_dist
    all_native = all(
        d < get_min_adjacent_edge_length(eo2['edge'], eo2['shape'])
        and eo2['body'] is not None
        for eo2 in edge_list
    )

    doc.openTransaction("Full Chamfer")
    try:
        base_shape = edge_list[0]['shape']
        done_by_feature = False

        if all_native:
            # 小半径 → PartDesign Chamfer feature
            body = edge_list[0]['body']
            tip = get_tip(body)
            if tip is None:
                raise RuntimeError("无法获取 Body 的 Tip feature")
            edge_names = [eo2['sub'] for eo2 in edge_list]
            chamfer = doc.addObject('PartDesign::Chamfer', 'Chamfer')
            body.addObject(chamfer)
            chamfer.Base = (tip, edge_names)
            chamfer.Size = d
            body.recompute()
            done_by_feature = True
        else:
            # 大半径 → 先试 shape.makeChamfer, 失败则布尔切割
            new_shape = None
            try:
                edges = [base_shape.Edges[int(eo2['sub'].replace('Edge',''))-1]
                         for eo2 in edge_list]
                new_shape = base_shape.makeChamfer(d, d, edges)
            except Exception:
                pass

            if new_shape is None or new_shape.isNull():
                cutters = []
                for eo2 in edge_list:
                    e_idx = int(eo2['sub'].replace('Edge', '')) - 1
                    cutter = create_chamfer_cutter(base_shape, e_idx, d)
                    if cutter is None or cutter.isNull():
                        raise RuntimeError(f"边 {eo2['sub']} 切割体构造失败")
                    cutters.append(cutter)

                combined_cutter = cutters[0]
                for c in cutters[1:]:
                    combined_cutter = combined_cutter.fuse(c)
                new_shape = base_shape.cut(combined_cutter)

            if new_shape is None or new_shape.isNull():
                raise RuntimeError("倒角生成失败")

            body = edge_list[0]['body']
            obj = edge_list[0]['obj']
            if body:
                result_obj = doc.addObject('PartDesign::Feature', 'FullChamfer')
                result_obj.Shape = new_shape.removeSplitter()
                result_obj.Label = "FullChamfer"
                body.addObject(result_obj)
                obj.Visibility = False
                body.recompute()
            else:
                obj.Shape = new_shape
                doc.recompute()

        doc.commitTransaction()
        App.Console.PrintMessage(
            f"FullChamfer: {len(edge_list)} 条边, 距离: {d:.4f} mm\n")

    except Exception as e:
        doc.abortTransaction()
        QtGui.QMessageBox.critical(None, "倒角失败", str(e))


if __name__ == '__main__':
    main()
