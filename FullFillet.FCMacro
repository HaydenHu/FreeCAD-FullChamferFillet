# -*- coding: utf-8 -*-
# Macro: FullFillet
# 图标: 完全圆角
# 功能: 对选中的边执行完全圆角（圆角面完全覆盖相邻侧面）
# 原理: 构造带圆弧截面的切割体 + 布尔差集实现完全圆角
#
# 使用方法:
#   1. 在 PartDesign 工作台中选中一条或多条边
#   2. 运行此宏
#   3. 输入圆角半径（默认=相邻面最小边长/2=完全圆角）

import FreeCAD as App
import FreeCADGui as Gui
import Part
from FreeCAD import Vector
from PySide import QtGui, QtCore
import math


def get_adjacent_faces(edge, shape):
    """获取包含此边的所有面."""
    mid_p = (edge.FirstParameter + edge.LastParameter) / 2.0
    mid_pt = edge.valueAt(mid_p)
    faces = []
    for f in shape.Faces:
        try:
            d, _, _ = f.distToShape(Part.Vertex(mid_pt))
            if d < 1e-5:
                faces.append(f)
        except Exception:
            pass
    return faces


def edges_same(e1, e2, tol=1e-5):
    mid1 = (e1.FirstParameter + e1.LastParameter) / 2.0
    mid2 = (e2.FirstParameter + e2.LastParameter) / 2.0
    if e1.valueAt(mid1).distanceToPoint(e2.valueAt(mid2)) > tol:
        return False
    return abs(e1.Length - e2.Length) < tol


def get_min_adjacent_edge_length(selected_edge, shape):
    min_len = float('inf')
    for face in get_adjacent_faces(selected_edge, shape):
        for other_edge in face.Edges:
            if edges_same(other_edge, selected_edge):
                continue
            L = other_edge.Length
            if L > 1e-7 and L < min_len:
                min_len = L
    return min_len if min_len != float('inf') else 0.0


def find_body(obj):
    if obj.TypeId == 'PartDesign::Body':
        return obj
    for p in obj.InList:
        if p.TypeId == 'PartDesign::Body':
            return p
    try:
        g = obj.getParentGroup()
        if g and g.TypeId == 'PartDesign::Body':
            return g
    except Exception:
        pass
    return None


def get_tip(body):
    if hasattr(body, 'Tip') and body.Tip:
        return body.Tip
    for o in reversed(body.Group):
        if hasattr(o, 'Shape') and not o.Shape.isNull():
            return o
    return None


def create_fillet_cutter(shape, edge_idx, fillet_radius):
    """构造圆角切割体——截面+extrude 双向拉伸."""
    edge = shape.Edges[edge_idx]
    r = fillet_radius

    # 参数方式获取起终点（兼容圆形边）
    fp = edge.FirstParameter
    lp = edge.LastParameter
    v0 = edge.valueAt(fp)
    v1 = edge.valueAt(lp)
    if v0.distanceToPoint(v1) < 1e-5:
        v1 = edge.valueAt(fp + (lp - fp) / 2.0)
    el = (v1 - v0).Length

    # 中点切线
    mid_p = (fp + lp) / 2.0
    ev = edge.tangentAt(mid_p)
    ev.normalize()

    # 相邻面
    adj_faces = get_adjacent_faces(edge, shape)
    normals = []
    for f in adj_faces:
        n = f.normalAt(0.5, 0.5)
        normals.append(n)

    if len(normals) < 2:
        raise RuntimeError("边至少需要两个相邻面")

    n0, n1 = normals[0], normals[1]
    for i, (n, f) in enumerate([(n0, adj_faces[0]), (n1, adj_faces[1])]):
        center = f.CenterOfMass
        if n.dot(center - v0) < 0:
            normals[i] = -n
    n0, n1 = normals[0], normals[1]

    cut0 = -n0
    cut1 = -n1

    # 投影到垂直于ev的平面构成2D坐标系
    x_dir = cut0 - ev * cut0.dot(ev)
    x_dir.normalize()
    y_dir = cut1 - ev * cut1.dot(ev)
    y_dir.normalize()

    def pt(a, b):
        return v0 + x_dir * a + y_dir * b

    # 截面: origin→直边→弧→直边→origin
    mid_angle = 5 * math.pi / 4
    mid_pt = pt(r + r * math.cos(mid_angle), r + r * math.sin(mid_angle))
    arc = Part.Arc(pt(r, 0), mid_pt, pt(0, r))

    w_edges = [
        Part.makeLine(pt(0, 0), pt(r, 0)),
        arc.toShape(),
        Part.makeLine(pt(0, r), pt(0, 0)),
    ]

    wire = Part.Wire(w_edges)
    face = Part.Face(wire)

    if face.isNull():
        raise RuntimeError("无法创建切割截面")

    ext_dist = el + 20
    sweep = face.extrude(ev * ext_dist)
    sweep2 = face.extrude(-ev * ext_dist)
    return sweep.fuse(sweep2)


def main():
    doc = App.ActiveDocument
    if not doc:
        QtGui.QMessageBox.warning(None, "错误", "请先打开文档。")
        return

    sel = Gui.Selection.getSelectionEx()
    if not sel:
        QtGui.QMessageBox.warning(None, "错误", "请先选中一条或多条边。")
        return

    edge_list = []
    for s in sel:
        if not hasattr(s.Object, 'Shape'):
            continue
        obj = s.Object
        shape = obj.Shape
        body = find_body(obj)
        for sn in s.SubElementNames:
            if sn.startswith('Edge'):
                try:
                    edge_list.append({
                        'edge': shape.getElement(sn),
                        'shape': shape,
                        'body': body,
                        'obj': obj,
                        'sub': sn,
                    })
                except Exception:
                    pass

    if not edge_list:
        QtGui.QMessageBox.warning(None, "错误", "未获取到有效边。")
        return

    def get_default_fillet_radius(edge, shape):
        """获取默认圆角半径：圆边用圆半径，直边用最小邻边长."""
        try:
            c = edge.Curve
            if hasattr(c, 'Radius') and c.Radius > 0:
                return c.Radius, True
        except Exception:
            pass
        min_l = get_min_adjacent_edge_length(edge, shape)
        return min_l, False

    edge_data = []
    for eo in edge_list:
        default_r, is_circle = get_default_fillet_radius(eo['edge'], eo['shape'])
        min_l = get_min_adjacent_edge_length(eo['edge'], eo['shape'])
        if default_r < 1e-7:
            QtGui.QMessageBox.warning(None, "错误",
                f"边 {eo['sub']} 无法计算参数。")
            return
        edge_data.append({'eo': eo, 'default_r': default_r,
                          'min_len': min_l, 'is_circle': is_circle})

    # 对话框
    dlg = QtGui.QDialog()
    dlg.setWindowTitle("完全圆角")
    dlg.setMinimumWidth(380)
    dlg.setModal(True)
    layout = QtGui.QVBoxLayout()

    layout.addWidget(QtGui.QLabel(
        f"<b>完全圆角</b><br>已选中 {len(edge_list)} 条边"))
    layout.addSpacing(8)

    dist_layout = QtGui.QHBoxLayout()
    dist_layout.addWidget(QtGui.QLabel("圆角半径 (mm):"))
    radius_spin = QtGui.QDoubleSpinBox()
    radius_spin.setRange(0.001, 99999.0)
    radius_spin.setDecimals(4)
    radius_spin.setSingleStep(0.1)
    radius_spin.setValue(edge_data[0]['default_r'])
    dist_layout.addWidget(radius_spin)
    layout.addLayout(dist_layout)

    layout.addSpacing(4)

    info_text = "各边参数:\n"
    for i, ed in enumerate(edge_data):
        typ = "圆边" if ed['is_circle'] else "直边"
        info_text += (f"  边 {i + 1} ({typ}): 默认 {ed['default_r']:.4f} mm"
                      f"  最小邻边长 {ed['min_len']:.4f} mm\n")
    layout.addWidget(QtGui.QLabel(info_text))

    layout.addSpacing(4)

    scale_layout = QtGui.QHBoxLayout()
    scale_layout.addWidget(QtGui.QLabel("缩放因子:"))
    scale_slider = QtGui.QSlider(QtCore.Qt.Horizontal)
    scale_slider.setRange(1, 200)
    scale_slider.setValue(100)
    scale_label = QtGui.QLabel("1.00")
    scale_layout.addWidget(scale_slider)
    scale_layout.addWidget(scale_label)
    layout.addLayout(scale_layout)

    def on_slider(v):
        scale_label.setText(f"{v / 100.0:.2f}")
        r = edge_data[0]['default_r'] * v / 100.0
        radius_spin.setValue(r)

    def on_spin(v):
        if edge_data[0]['default_r'] > 0:
            s = int(v / edge_data[0]['default_r'] * 100)
            scale_slider.blockSignals(True)
            scale_slider.setValue(max(1, min(200, s)))
            scale_slider.blockSignals(False)
            scale_label.setText(f"{max(1, min(200, s)) / 100.0:.2f}")

    scale_slider.valueChanged.connect(on_slider)
    radius_spin.valueChanged.connect(on_spin)

    layout.addSpacing(8)

    btn_layout = QtGui.QHBoxLayout()
    ok = QtGui.QPushButton("执行圆角")
    ok.clicked.connect(dlg.accept)
    cancel = QtGui.QPushButton("取消")
    cancel.clicked.connect(dlg.reject)
    btn_layout.addWidget(ok)
    btn_layout.addWidget(cancel)
    layout.addLayout(btn_layout)
    dlg.setLayout(layout)

    if dlg.exec_() != QtGui.QDialog.Accepted:
        return

    radius = radius_spin.value()
    if radius <= 0:
        return

    r = radius
    all_native = all(
        r < get_min_adjacent_edge_length(eo2['edge'], eo2['shape'])
        and eo2['body'] is not None
        for eo2 in edge_list
    )

    doc.openTransaction("Full Fillet")
    try:
        base_shape = edge_list[0]['shape']
        done_by_feature = False

        if all_native:
            # 小半径 → PartDesign Fillet feature
            body = edge_list[0]['body']
            tip = get_tip(body)
            if tip is None:
                raise RuntimeError("无法获取 Body 的 Tip feature")
            edge_names = [eo2['sub'] for eo2 in edge_list]
            fillet = doc.addObject('PartDesign::Fillet', 'Fillet')
            body.addObject(fillet)
            fillet.Base = (tip, edge_names)
            fillet.Radius = r
            body.recompute()
            done_by_feature = True
        else:
            # 大半径 → 先试 shape.makeFillet, 失败则布尔切割
            new_shape = None
            try:
                edges = [base_shape.Edges[int(eo2['sub'].replace('Edge',''))-1]
                         for eo2 in edge_list]
                new_shape = base_shape.makeFillet(r, edges)
            except Exception:
                pass

            if new_shape is None or new_shape.isNull():
                cutters = []
                for eo2 in edge_list:
                    e_idx = int(eo2['sub'].replace('Edge', '')) - 1
                    cutter = create_fillet_cutter(base_shape, e_idx, r)
                    if cutter is None or cutter.isNull():
                        raise RuntimeError(f"边 {eo2['sub']} 切割体构造失败")
                    cutters.append(cutter)

                combined_cutter = cutters[0]
                for c in cutters[1:]:
                    combined_cutter = combined_cutter.fuse(c)
                new_shape = base_shape.cut(combined_cutter)

            if new_shape is None or new_shape.isNull():
                raise RuntimeError("圆角生成失败")

            body = edge_list[0]['body']
            obj = edge_list[0]['obj']
            if body:
                result_obj = doc.addObject('PartDesign::Feature', 'FullFillet')
                result_obj.Shape = new_shape.removeSplitter()
                result_obj.Label = "FullFillet"
                body.addObject(result_obj)
                obj.Visibility = False
                body.recompute()
            else:
                obj.Shape = new_shape
                doc.recompute()

        doc.commitTransaction()
        App.Console.PrintMessage(
            f"FullFillet: {len(edge_list)} 条边, 半径: {r:.4f} mm\n")

    except Exception as e:
        doc.abortTransaction()
        QtGui.QMessageBox.critical(None, "圆角失败", str(e))


if __name__ == '__main__':
    main()
